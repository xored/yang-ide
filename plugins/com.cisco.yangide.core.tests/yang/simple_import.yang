module my-crypto {
    namespace "http://example.com/my-crypto";
    prefix mc;
    
    import "crypto-base" {
        prefix "crypto";
    }
    
    identity aes {
        base "crypto:crypto-alg";
    }
    
    leaf crypto {
        type identityref {
            base "crypto:crypto-alg";
        }
    }
}
